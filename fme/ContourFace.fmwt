FME workspace ContourFace.fmwt
Title: ContourFace
History: 2014-01-16,DBagh,Created

Parameters:
- SourceDataset_JPEG = $(FME_MF_DIR)1/Images/Dale.jpg   # Source JPEG File(s)
- BACKGROUND_IMAGE = $(FME_SHAREDRESOURCE_DATA)/backgrounds/Wood.jpg

Readers:
- SHAPE_1: SHAPE from $(FME_MF_DIR)1/Contours/Contours.shp
- JPEG_1: JPEG from $(SourceDataset_JPEG)

Writers:
- JPEG_2: JPEG to C:\Users\dbagh\Dropbox (Safe Software Inc.)\Mapnik - May Webinar\Demos\Face2Contours\Output

JPEG (reader JPEG_1)
    -> RasterPropertiesExtractor
Note: Number of columns and rows is needed for defining the image orientation - prtrait or lanscape
RasterPropertiesExtractor
    -> Tester
Note: Reduce to 100 pixels along longer side
RasterResampler
    ROWCOL_OR_CELLSIZE = Percentage
    PERCENTAGE = 100.0/@Value(_num_rows)*100
    INTERPOLATION_TYPE_NAME = Bicubic
    RESAMPLED -> RasterExpressionEvaluator
    RESAMPLED -> FeatureMerger_2 [input 2]
Note: Make a single band greyscale, 9 grades image
RasterExpressionEvaluator
    MODE = One Raster
    EXPRESSION_LIST = INTERPRETATION_LIST "UINT8" EXPRESSION_LIST "(0.2989*A[0] + 0.5870*A[1] + 0.1140*A[2])/25"
    RESULT -> FeatureMerger [input 1]
Contours (reader SHAPE_1)
    attributes: elevation number(30,10)
    -> BoundingBoxAccumulator
    -> FeatureMerger_2 [input 1]
BoundingBoxAccumulator
    TOPFER_INDEX = No
    BOUNDING_BOX -> BoundsExtractor
Note: Bounds will be needed for georeferencing the image
BoundsExtractor
    YMIN = _ymin
    ZMIN = _zmin
    XMIN = _xmin
    XMAX = _xmax
    ZMAX = _zmax
    YMAX = _ymax
    -> FeatureMerger [input 2]
Note: Join the extents of the contours to image for georeferencing
FeatureMerger
    PROCESS_DUPS = No
    MERGE_TYPE = Attributes Only
    SUPPLIERS_FIRST = No
    JOIN_KEYS = 0 0 AUTO
    SUPPLIER_PREFIX_DUMMY = YES
    MERGED -> RasterGeoreferencer
Note: Georeference the image
RasterGeoreferencer
    X_UR_COORD = @Value(_xmax)
    X_LR_COORD = @Value(_xmax)
    X_UL_COORD = @Value(_xmin)
    POINTANDANGLE_OR_EXTENTS = Extents
    Y_LL_COORD = @Value(_ymin)
    Y_LR_COORD = @Value(_ymin)
    X_LL_COORD = @Value(_xmin)
    Y_UR_COORD = @Value(_ymax)
    Y_UL_COORD = @Value(_ymax)
    -> RasterToPolygonCoercer
Note: Make polygons from raster
RasterToPolygonCoercer
    EXTRACT_NODATA = No
    LABEL_ATTRIBUTE = _label
    PRESERVE_ATTRIBUTES = Yes
    POLYGONS -> Generalizer
Note: Smooth rectangular shapes of polygons
Generalizer
    DISPLACEMENT = 1
    ALG_TEXT = McMaster (Smooth)
    PRESERVE = Yes
    NUMNEIGHBORS = 2
    -> Clipper_3 [input 1]
Note: Join imageattributes to contours for transferring rotation attribute - / needed for backward rotation of the landscape images
FeatureMerger_2
    PROCESS_DUPS = No
    MERGE_TYPE = Attributes Only
    SUPPLIERS_FIRST = No
    JOIN_KEYS = 0 0 AUTO
    SUPPLIER_PREFIX_DUMMY = YES
    MERGED -> Clipper_3 [input 2]
Note: Clip original contour to face polygons
Clipper_3
    CREATE_AGGREGATES = Yes
    CLIPPED_ATTR = _clipped
    MERGE_ATTRS = Yes
    PRESERVE_CLIPPEE_EXTENTS = No
    CLIP_TYPE = Multiple Clippers
    BOUNDARY_CASES = Treat as Inside
    INSIDE -> AttributeValueMapper_2
    OUTSIDE -> AttributeValueMapper_2
Note: Map palette values to line width
AttributeValueMapper_2
    DIRECTION = Forward (Source To Destination)
    VAL_ATTR = _thickness
    DEFAULT_VALUE = 1
    LUT = 0,8,1,7,2,6,3,5,4,3.75,5,2.75,6,2,7,1.5,8,1,9,0.75,10,0.5
    SRC = _label
    -> AttributeCreator_2
AttributeCreator_2
    ATTR_LIST = _line_color,"FME_CONDITIONAL:DEFAULT_VALUE'0,0,0'BOOL_OP;OR;COMPOSITE_TEST;<Unused>;TEST $(BACKGROUND_IMAGE) CONTAINS Wood'0.219608,0,0'BOOL_OP;OR;COMPOSITE_TEST;<Unused>;TEST $(BACKGROUND_IMAGE) CONTAINS Notebook.jpg'0.2,0.4,1'FME_NUM_CONDITIONS3___"
    -> MapnikRasterizer_2
Note: Rasterize contours using width set in ValueMapper
MapnikRasterizer_2
    GROUP_BY = _rotation
    BACKGROUND_IMAGE = $(BACKGROUND_IMAGE)
    INTERPRETATION_TYPE = RGB24
    BACKGROUND_COLOR_ALPHA = 1
    COLROW_OR_SPACING = Spacing
    SPACING = 250
    MAPNIK_CONFIG = Face;line;color-group;;stroke;@Value(_line_color);stroke-opacity;1;line-style-group;;stroke-width;@Value(_thickness);stroke-linejoin;miter;stroke-linecap;round;stroke-dasharray;"20 1";stroke-miterlimit;4;positioning-group;;offset;0;smoothing-group;;stroke-gamma;1;stroke-gamma-method;power;smooth;1;rasterizer;full;comp-group;;comp-op;multiply
    BACKGROUND_COLOR = 1,1,1
    SPECIFY_GROUND_EXTENTS = Use input data ground extents
    RASTER -> Tester_2
TimeStamper
    FMT = FME Date/Time (^Y^m^d^H^M^S)
    TIME_ATTR = _timestamp
    -> ContourFace (writer JPEG_2)
ContourFace (writer JPEG_2)

Bookmark: Rotate if landscape
Tester
    TEST_MODE = Automatic
    TEST_DESCRIPTION = ""
    BOOL_OP = OR
    TEST_CLAUSE = TEST @Evaluate(@Value(_num_columns)/@double(@Value(_num_rows))) > 1
    PASSED -> AttributeCreator
    FAILED -> RasterResampler
AttributeCreator
    ATTR_LIST = _rotation,-90
    -> Rotator
Rotator
    YORIG = 0
    ANGLE = @Value(_rotation)
    XORIG = 0
    ROTATED -> RasterResampler

Bookmark: If original is landscape rotate back to this orientation
Tester_2
    TEST_MODE = Automatic
    TEST_DESCRIPTION = ""
    BOOL_OP = OR
    TEST_CLAUSE = TEST _rotation NOT_ATTRIBUTE_IS_MISSING ""
    PASSED -> Rotator_2
    FAILED -> TimeStamper
Rotator_2
    YORIG = 0
    ANGLE = -@Value(_rotation)
    XORIG = 0
    ROTATED -> TimeStamper
